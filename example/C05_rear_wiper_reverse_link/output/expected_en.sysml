package C05RearWiperReverseLink {
    doc /*
    C05 Rear Wiper Reverse Link
    This case links a rear wiper one-wipe action to reverse gear when the front wiper is already active.
    */

    item def WiperStatusValue;
    item def ShiftPositionValue;
    item def WiperCommandValue;

    port def WiperStatusPort {
        in item frontWiperActive : WiperStatusValue;
    }

    port def ShiftPositionPort {
        in item shiftPosition : ShiftPositionValue;
    }

    port def WiperCommandPort {
        out item rearWiperCommand : WiperCommandValue;
    }

    interface def RearWiperCommandInterface {
        end source : WiperCommandPort;
        end target : ~WiperCommandPort;
        flow source.rearWiperCommand to target.rearWiperCommand;
    }

    requirement def Req001 {
        doc /*
        C05-RQ-001: When reverse gear is engaged while the front wiper is active, the system shall command one rear-wiper wipe within 1 s.
        */
    }

    requirement def Req002 {
        doc /*
        C05-RQ-002: The system shall not issue more than one reverse-linked rear-wiper wipe within 10 s.
        */
    }

    requirement def Req003 {
        doc /*
        C05-RQ-003: The system shall disable the reverse-linked wipe while the rear wiper service mode is active.
        */
    }

    part def RearWiperController {
        port frontWiperIn : WiperStatusPort;
        port shiftIn : ShiftPositionPort;
        port commandOut : WiperCommandPort;
    }

    part def RearWiperMotor {
        port commandIn : ~WiperCommandPort;
    }

    part def RearWiperLinkSystem {
        part controller : RearWiperController;
        part motor : RearWiperMotor;
    }

    part systemUnderTest : RearWiperLinkSystem;

    requirement requirement_001 : Req001;
    requirement requirement_002 : Req002;
    requirement requirement_003 : Req003;

    package ViewDefinitions {
        private import Views::*;
        private import DS_Views::*;

        view systemContextView : DS_Views::SymbolicViews::gv {
            expose C05RearWiperReverseLink::systemUnderTest;
            expose C05RearWiperReverseLink::systemUnderTest::controller;
            expose C05RearWiperReverseLink::systemUnderTest::motor;
        }
    }
}
